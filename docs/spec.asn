--<ASN1.PDU CryptoConditions.Condition, CryptoConditions.Fulfillment>--

CryptoConditions
DEFINITIONS
AUTOMATIC TAGS ::=
BEGIN

	/**
	 * CONTAINERS
	 */

	Condition ::= SEQUENCE {
		version INTEGER (0..255),
		type FulfillmentType,
		requiredSuites OCTET STRING,
		fingerprint OCTET STRING,
		maxFulfillmentLength INTEGER (0..MAX)
	}

	Fulfillment ::= SEQUENCE {
		version INTEGER (0..255),
		type FulfillmentType,
		payload OCTET STRING
	}

	FulfillmentType ::= INTEGER {
		preimageSha256(0),
		rsaSha256(1),
		prefixSha256(2),
		thresholdSha256(3),
		ed25519(4)
	} (0..65535)

	/**
	 * FULFILLMENT PAYLOADS
	 */

	-- For preimage conditions, the payload *is* the preimage

	PrefixSha256FulfillmentPayload ::= SEQUENCE {
		prefix OCTET STRING,
		subfulfillment Fulfillment
	}

	ThresholdSha256FulfillmentPayload ::= SEQUENCE {
		threshold INTEGER (0..4294967295),
		subfulfillments SEQUENCE OF ThresholdSubfulfillment
	}

	ThresholdSubfulfillment ::= SEQUENCE {
		weight INTEGER (0..4294967295) DEFAULT 1,
		condition Condition OPTIONAL,
		fulfillment Fulfillment OPTIONAL
	}

	RsaSha256FulfillmentPayload ::= SEQUENCE {
		modulus OCTET STRING (SIZE(128..512)),
		signature OCTET STRING (SIZE(128..512))
	}

	Ed25519FulfillmentPayload ::= SEQUENCE {
		publicKey OCTET STRING (SIZE(32)),
		signature OCTET STRING (SIZE(64))
	}

	/**
	 * FINGERPRINTS
	 */

	-- SHA-256 hash of the fingerprint contents
	Sha256Fingerprint ::= OCTET STRING (SIZE(32)) -- digest

	-- 32-byte Ed25519 public key
	Ed25519Fingerprint ::= OCTET STRING (SIZE(32)) -- publicKey

	/**
	 * FINGERPRINT CONTENTS
	 *
	 * The content that will be hashed to arrive at the fingerprint.
	 */

	-- The preimage type hashes the raw contents of the preimage

	PrefixSha256FingerprintContents ::= SEQUENCE {
		version INTEGER (0..255),
		type FulfillmentType,
		prefix OCTET STRING,
		condition Condition
	}

	ThresholdSha256FingerprintContents ::= SEQUENCE {
		version INTEGER (0..255),
		type FulfillmentType,
		threshold INTEGER (0..4294967295),
		subconditions SEQUENCE OF ThresholdSubcondition
	}

	ThresholdSubcondition ::= SEQUENCE {
		weight INTEGER (0..4294967295),
		condition Condition
	}

	RsaSha256FingerprintContents ::= INTEGER (0..MAX) -- modulus

	/**
	 * EXAMPLES
	 */

	exampleCondition Condition ::=
	{
		version 1,
		requiredSuites '1'B,
		fingerprint 'E3B0C44298FC1C149AFBF4C8996FB92427AE41E4649B934CA495991B7852B855'H,
		maxFulfillmentLength 2
	}

	exampleFulfillment Fulfillment ::=
	{
		version 1,
		type preimageSha256,
		payload '00'H
	}

	exampleRsaSha256FulfillmentPayload RsaSha256FulfillmentPayload ::=
	{
		modulus 'B30E7A938783BABF836850FF49E14F87E3F92D5C46E33FECA3E4F0B22358580B11765995F4B8EEA7FB4712C2E1E316F7F775A953D232216A169D9A64DDC007120A400B37F2AFC077B62FE304DE74DE6A119EC4076B529C4F6096B0BAAD4F533DF0173B9B822FD85D65FA4BEFA92D8F524F69CBCA0136BD80D095C169AEC0E095'H,
		signature '48E8945EFE007556D5BF4D5F249E4808F7307E29511D3262DAEF61D88098F9AA4A8BC0623A8C975738F65D6BF459D543F289D73CBC7AF4EA3A33FBF3EC4440447911D72294091E561833628E49A772ED608DE6C44595A91E3E17D6CF5EC3B2528D63D2ADD6463989B12EEC577DF6470960DF6832A9D84C360D1C217AD64C8625BDB594FB0ADA086CDECBBDE580D424BF9746D2F0C312826DBBB00AD68B52C4CB7D47156BA35E3A981C973863792CC80D04A180210A52415865B64B3A61774B1D3975D78A98B0821EE55CA0F86305D42529E10EB015CEFD402FB59B2ABB8DEEE52A6F2447D2284603D219CD4E8CF9CFFDD5498889C3780B59DD6A57EF7D732620'H
	}

	exampleEd25519FulfillmentPayload Ed25519FulfillmentPayload ::=
	{
		publicKey 'EC172B93AD5E563BF4932C70E1245034C35467EF2EFD4D64EBF819683467E2BF'H,
		signature 'B62291FAD9432F8F298B9C4A4895DBE293F6FFDA1A68DADF0CCDEF5F47A0C7212A5FEA3CDA97A3F4C03EA9F2E8AC1CEC86A51D452127ABDBA09D1B6F331C070A'H
	}

END
